package AcpdCdd_SysMLv2 {
    package Output {

        private import ScalarValues::*;
        private import AcpdCdd_SysMLv2::Types::*;
	private import ScalarValues::Boolean;
        private import AcpdCdd_SysMLv2::AUTOSAR_CDD_FunctionKinds::*;
        private import AcpdCdd_SysMLv2::SWFailureCatalogue::*;
port def AcceleratorDataInPort {
            in item acceleratorData : tAcpdCdd_rc_AccrSnsr;
        }

        port def RteDataOutPort {
            out item RteData : tAcpdCdd_rc_AccrSnsr;
        }

        // trlc-satisfies: 25094008
        // trlc-satisfies: 44879821
        // trlc-satisfies: 25131815
        // trlc-satisfies: 25131787
        action def AcpdCdd_UpdateOutput :> ModuleApiFunction {
            in item acceleratorData : tAcpdCdd_rc_AccrSnsr;
            out item RteData : tAcpdCdd_rc_AccrSnsr;
action CheckAcceleratorDataPointer {
                in item acceleratorData : tAcpdCdd_rc_AccrSnsr;
                out item validAcceleratorData : tAcpdCdd_rc_AccrSnsr;
                out item invalidAcceleratorData : tAcpdCdd_rc_AccrSnsr;
            }
            attribute CheckAcceleratorDataPointer_allows_ConvertAcpdCddDataTypeToRteType : Boolean;
            attribute CheckAcceleratorDataPointer_allows_UseDefaultErrorValuesIfNull : Boolean;
            action UseDefaultErrorValuesIfNull {
                in item invalidAcceleratorData : tAcpdCdd_rc_AccrSnsr;
                out item defaultRteData : tAcpdCdd_rc_AccrSnsr;
            }
            // trlc-satisfies: 25094059
            action ConvertAcpdCddDataTypeToRteType {
                in item validAcceleratorData : tAcpdCdd_rc_AccrSnsr;
                out item convertedRteData : tAcpdCdd_rc_AccrSnsr;
            }
            action CopySensor1Data;
            action CopySensor2Data;
            action CopySupply1Data;
            action CopySupply2Data;
            action MergeRteData {
                in item convertedRteData : tAcpdCdd_rc_AccrSnsr;
                in item defaultRteData : tAcpdCdd_rc_AccrSnsr;
                out item mergedRteData : tAcpdCdd_rc_AccrSnsr;
            }
            action Rte_Write_AcpdCdd_rc_AccrSnsrVcc_AcpdCdd_rc_SnsrVcc {
                in item mergedRteData : tAcpdCdd_rc_AccrSnsr;
                out item RteData : tAcpdCdd_rc_AccrSnsr;
            }
            action Return;
flow from acceleratorData to CheckAcceleratorDataPointer.acceleratorData;
                first CheckAcceleratorDataPointer if CheckAcceleratorDataPointer_allows_ConvertAcpdCddDataTypeToRteType then ConvertAcpdCddDataTypeToRteType;
                first CheckAcceleratorDataPointer if not CheckAcceleratorDataPointer_allows_ConvertAcpdCddDataTypeToRteType then UseDefaultErrorValuesIfNull;
flow from CheckAcceleratorDataPointer.validAcceleratorData to ConvertAcpdCddDataTypeToRteType.validAcceleratorData;
            flow from CheckAcceleratorDataPointer.invalidAcceleratorData to UseDefaultErrorValuesIfNull.invalidAcceleratorData;
            first ConvertAcpdCddDataTypeToRteType then CopySensor1Data;
            first CopySensor1Data then CopySensor2Data;
            first CopySensor2Data then CopySupply1Data;
            first CopySupply1Data then CopySupply2Data;
            first CopySupply2Data then MergeRteData;
            first UseDefaultErrorValuesIfNull then MergeRteData;
            flow from ConvertAcpdCddDataTypeToRteType.convertedRteData to MergeRteData.convertedRteData;
            flow from UseDefaultErrorValuesIfNull.defaultRteData to MergeRteData.defaultRteData;
            first MergeRteData then Rte_Write_AcpdCdd_rc_AccrSnsrVcc_AcpdCdd_rc_SnsrVcc;
            flow from MergeRteData.mergedRteData to Rte_Write_AcpdCdd_rc_AccrSnsrVcc_AcpdCdd_rc_SnsrVcc.mergedRteData;
            first Rte_Write_AcpdCdd_rc_AccrSnsrVcc_AcpdCdd_rc_SnsrVcc then Return;
            flow from Rte_Write_AcpdCdd_rc_AccrSnsrVcc_AcpdCdd_rc_SnsrVcc.RteData to RteData;
item nullInputDefaultNotAppliedFailure : DefaultValueNotApplied {
                attribute localEffect = "NULL input is not converted to default/error output values.";
            }

            item incorrectRteOutputFailure : IncorrectOutputData {
                attribute localEffect = "RTE output data does not consistently represent the qualified accelerator data.";
            }
}
        action AcpdCdd_Output_Behavior {
attribute ReceiveAcceleratorData_allows_AcpdCdd_UpdateOutput : Boolean;
            attribute ReceiveAcceleratorData_allows_WriteSafeDefaultOutput : Boolean;
            action ReceiveAcceleratorData;
            action AcpdCdd_UpdateOutput : ModuleApiFunction;
            action WriteSafeDefaultOutput;
            action WriteRteOutput;

                first ReceiveAcceleratorData if ReceiveAcceleratorData_allows_AcpdCdd_UpdateOutput then AcpdCdd_UpdateOutput;
                first ReceiveAcceleratorData if not ReceiveAcceleratorData_allows_AcpdCdd_UpdateOutput then WriteSafeDefaultOutput;
first AcpdCdd_UpdateOutput then WriteRteOutput;
            first WriteSafeDefaultOutput then WriteRteOutput;
        }

        part def AcpdCdd_Output {
            port acceleratorDataIn : AcceleratorDataInPort;
            port rteDataOut : RteDataOutPort;

            action updateOutput;
            action outputBehavior;
        }

        action AcpdCdd_Output_Sequence_AsActionFlow {
attribute OutputReceivesAcceleratorData_allows_OutputPreparesRteData : Boolean;
            attribute OutputReceivesAcceleratorData_allows_OutputRequestsSafeDefaultTransmission : Boolean;
            action OutputReceivesAcceleratorData;
            action OutputReceivesMonitoringStatus;
            action OutputPreparesRteData;
            action OutputRequestsSafeDefaultTransmission;
            action OutputRequestsRteTransmission;
            action RtePublishesOutputData;

            first OutputReceivesAcceleratorData then OutputReceivesMonitoringStatus;
                first OutputReceivesMonitoringStatus if OutputReceivesAcceleratorData_allows_OutputPreparesRteData then OutputPreparesRteData;
                first OutputReceivesMonitoringStatus if not OutputReceivesAcceleratorData_allows_OutputPreparesRteData then OutputRequestsSafeDefaultTransmission;
first OutputPreparesRteData then OutputRequestsRteTransmission;
            first OutputRequestsSafeDefaultTransmission then OutputRequestsRteTransmission;
            first OutputRequestsRteTransmission then RtePublishesOutputData;
        }


    }
}
